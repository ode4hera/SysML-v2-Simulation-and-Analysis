package TMS_SystemRequirements_Example {
    doc 
    /*
    * [ISO 15288 6.4.3.1] The purpose of the System Requirements Definition process is to
    * transform the stakeholder, user-oriented view of desired capabilities into a technical
    * view of a solution that meets the operational needs of the user.
    * 
    * [MagicGrid] The System Requirement process within the Solution Domain.
    */
    private import RequirementsManagement::*;

    // System Definition 
    abstract part def ThermalManagementUnit {  // replace with ThermalManagementSystem def in SA
        attribute maxRejectedHeat : ISQ::HeatFlowRateValue;
        attribute maxEnergyConsumption : ISQ::EnergyValue;
        attribute mass : ISQ::MassValue;
        attribute volume : ISQ::VolumeValue;
        attribute powerUpTime: ISQ::TimeValue;
        attribute powerUpRejectedHeat : ISQ::HeatFlowRateValue;
    }
 

    // System Requirements
    requirement <'R-000'> rejectHeatRequirement : Requirement {
        doc /* The thermal management system shall reject heat */
        subject tmu: ThermalManagementUnit;
        require heatLoadRequirement;
        action rejectHeat;
        attribute redefines rationale = "Dissipate heat generated by OBS";
        attribute :>> source = "OBS performance";
        :>> status = ReqStatus::Approved;
        :>> version = "1.0";
        :>> priority = ReqPriority::MustHave;
        :>> implementationStatus = ReqImplementationStatus::InProgress;
        :>> verificationStatus = VVStatus::NotStarted;
    }
    requirement <'R-001'> heatLoadRequirement : Requirement {
        doc /* The thermal management system shall reject up to 100 kW of heat. */
        subject tmu: ThermalManagementUnit;
        attribute heatLoadLimit : ISQ::HeatFlowRateValue = 100[SI::kW];
        require constraint { tmu.maxRejectedHeat >= heatLoadLimit }
        attribute redefines rationale = "Dissipate heat generated by OBS";
        attribute :>> source = "OBS performance";
        :>> status = ReqStatus::Approved;
        :>> version = "1.0";
        :>> priority = ReqPriority::MustHave;
        :>> implementationStatus = ReqImplementationStatus::InProgress;
        :>> verificationStatus = VVStatus::NotStarted;
    }
    requirement <'R-002'> energyConsumptionRequirement : Requirement {
        doc /* The thermal management system shall consume maximum 3000 kWh of energy. */
        subject tmu: ThermalManagementUnit;
        attribute energyConsumptionLimit : ISQ::EnergyValue = 3000e3[SI::'W⋅h'];
        require constraint { tmu.maxEnergyConsumption <= energyConsumptionLimit }
        attribute redefines rationale = "Energy consumption";
        attribute :>> source = "OBS energy budget";
        :>> status = ReqStatus::Approved;
        :>> version = "1.0";
        :>> priority = ReqPriority::MustHave;
        :>> implementationStatus = ReqImplementationStatus::InProgress;
        :>> verificationStatus = VVStatus::NotStarted;
    }
    requirement <'R-003'> massRequirement : Requirement {
        doc /* The thermal management system shall have maximum 500 kg of mass. */
        subject tmu: ThermalManagementUnit;
        attribute maxMass : ISQ::MassValue = 200[SI::kg];
        require constraint { tmu.mass <= maxMass }
        attribute redefines rationale = "Mass limit";
        attribute :>> source = "OBS mass budget";
        :>> status = ReqStatus::Approved;
        :>> version = "1.0";
        :>> priority = ReqPriority::MustHave;
        :>> implementationStatus = ReqImplementationStatus::InProgress;
        :>> verificationStatus = VVStatus::NotStarted;
    }
    requirement <'R-004'> volumeRequirement : Requirement {
        doc /* The thermal management system shall have maximum 2.5 m3 of volume. */
        subject tmu: ThermalManagementUnit;
        attribute maxVolume : ISQ::VolumeValue = 2.5[SI::'m³'];
        require constraint { tmu.volume <= maxVolume }
        attribute redefines rationale = "Volume limit";
        attribute :>> source = "OBS bay available space";
        :>> status = ReqStatus::Approved;
        :>> version = "1.0";
        :>> priority = ReqPriority::MustHave;
        :>> implementationStatus = ReqImplementationStatus::InProgress;
        :>> verificationStatus = VVStatus::NotStarted;
    }
    requirement <'R-005'> powerUpRequirement : Requirement {
        doc /* The thermal management system shall start-up in less than 2 min of time. */
        subject tmu: ThermalManagementUnit;
        attribute powerUpTimeLimit : ISQ::TimeValue = 2[SI::minute];
        attribute powerUpMinHeatLoad : ISQ::HeatFlowRateValue = 30[SI::kW];
        require constraint {tmu.powerUpRejectedHeat >= powerUpMinHeatLoad}
        require constraint { tmu.powerUpTime <= powerUpTimeLimit }
        attribute redefines rationale = "Power up constraint";
        attribute :>> source = "OBS boot procedure";
        :>> status = ReqStatus::Approved;
        :>> version = "1.0";
        :>> priority = ReqPriority::MustHave;
        :>> implementationStatus = ReqImplementationStatus::InProgress;
        :>> verificationStatus = VVStatus::NotStarted;
    }
    requirement <'R-006'> pressureDropRequirement : Requirement {
        doc /* The cooling circuit pump shall recover heat exchanger pressure drop . */
        subject tmu: ThermalManagementUnit;
        action increaseCircuitPressure;
        attribute redefines rationale = "Maintain circuit flow";
        attribute :>> source = "TMS specification";
        :>> status = ReqStatus::Approved;
        :>> version = "1.0";
        :>> priority = ReqPriority::MustHave;
        :>> implementationStatus = ReqImplementationStatus::InProgress;
        :>> verificationStatus = VVStatus::NotStarted;
    }

    // // System Instantiation (this is the outcome of the design process, inserted here only as example)
    // part <tms_1> thermalManagementSystem_1 : ThermalManagementUnit {
    //     :>> maxRejectedHeat = 132[SI::kW];
    //     :>> maxEnergyConsumption = 3200e3[SI::'W⋅h'];
    //     :>> mass = 350[SI::kg];
    //     :>> volume = 2.9[SI::'m³'];
    //     :>> powerUpTime = 0.9[SI::minute];
    //     :>> powerUpRejectedHeat = 39[SI::kW];

    // }
    // satisfy heatLoadRequirement by thermalManagementSystem_1;
    // satisfy energyConsumptionRequirement by thermalManagementSystem_1;
    // satisfy massRequirement by thermalManagementSystem_1;
    // satisfy volumeRequirement by thermalManagementSystem_1;
    // satisfy powerUpRequirement by thermalManagementSystem_1;


}
